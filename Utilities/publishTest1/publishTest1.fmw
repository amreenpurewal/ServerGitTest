FME workspace publishTest1.fmw

Creator
    NUM = 1
    GEOMTYPE = Geometry Object
    CREATED -> HTTPCaller
HTTPCaller
    RESPONSE_HEADER_LIST_ATTR = _headers
    TRANSFER_TIMEOUT_LENGTH = 90
    AUTH_USERNAME = admin
    HTTP_METHOD = PUT
    CONNECTION_TIMEOUT_LENGTH = 60
    STATUS_CODE_ATTR = _http_status_code
    VERIFY_SSL_CERTIFICATES = Yes
    AUTH_PASSWORD =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
    CUSTOM_HEADERS = Content-Type;application/octet-stream
    UPLOAD_FILE = C:\Users\apurewal\Documents\VersionControl\test1.fmw
    TARGET_URL = http://localhost:8080/fmerest/v3/repositories/Samples/items/test.fmw
    FOLLOW_REDIRECTS = Yes
    ERROR_ATTR = _error
    TARGET_ATTR_ENCODING = auto-detect
    UPLOAD_CONTENT_TYPE = Binary (application/octet-stream)
    SAVE_FILE = Attribute
    UPLOAD_TYPE = Upload From File
    AUTH_METHOD = Basic
    USE_COOKIES = No
    TARGET_ATTR = _response_body
    -> Logger
Logger
    MAXCOORDS = 20
    MESSAGE = Feature is:
    MAXFEATS = 20
